module TemperatureSensor {
  yang-version 1.1;
  namespace "urn:example:asn1-transpile:TemperatureSensor";
  prefix temperaturesensor;
  organization "transpiled from ASN.1";
  contact "transpiler";
  description "Generated by asn1_to_yang transpiler.";

  container TemperatureSensorObject {
    leaf statusLED {
      type enumeration {
        enum "green" { value 0; }
        enum "yellow" { value 1; }
        enum "red" { value 2; }
      }
      mandatory true;
    }
    leaf batteryLevel {
      type uint8 { range '0..100'; }
      mandatory true;
    }
    container temperature {
        leaf voltageADC {
          type decimal64 { fraction-digits 1; range "0.5..3.3"; }
          mandatory true;
        }
    }
  }

}
